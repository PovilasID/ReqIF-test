# IBM Rational DOORS, 24 May 2014

# Specification: Apgyvendinimo posistemė
- ReqIF.Name: Apgyvendinimo posistemė
- ReqIF.Name: Apgyvendinimo posistemė

## 1: Įvadas
Darbo tikslas sukurti sistemą galinčią kontroliuoti olimpinių žaidinių gyventojų srautus. Parinkti tinkamas apgyvendinimo vietas, nustatyti vizito trukmes, surinkti informaciją apie gyventoją.

### 2: Sistemos paskirtis

#### 3: Projekto kūrimos pagrindas
Sukurti sistemą galinčia aptarnauji olimpinių žaidinių gyventojų srautus ir juos nukreipti į tinkamos infrastruktūros pastatus.

#### 4: Sistemos tikslai
Sukurti išansktinės rezervacijos glaimybę.
Realizuoti rezervacijos valdymą.
Realizuoti lankytojų duomenų valdymą.
Turėti galimybę lankytojams pasiūlyti skirtingas infrastruktūras palei jų tipą.

### 5: Sistemos dalyviai

#### 7: Užsakovai, pirkėjai ir kiti sistema suinteresuoti asmenys
Olimpinių žaidynių komitetas.

#### 8: Naudotojai
Olimpinių žaidinių administracija atsakinga už apgyvendinimą.
Registratūros darbuotojai.

## 65: Projekto apribojimai
Skirstomi į techninius ir netechninius reikalvaimus.

### 66: Įpareigojantys apribojimai
Reikalavimai, kurių neįgyvedinus sistemos funkcinai ir nefunkciniai reikalavimai bus nepilnai ar visai neįgyvendinti.

#### 67: Apribojimai sprendimui
Sprendimas ribojamas savo funkciniais ir nefunkciniais reikalavimais.
Sprendimo funkcionalumas neturi persidengti su palaikančių ar sus sitema bendraujančių sistemų funkcionalumu.

#### 69: Diegimo aplinka
MINIMALŪS REIKALAVIMAI KLEIANTAMS
Nemažiau kaip trys paskirstyti serveriai
Serveriai:
Programinės įrangos reikalavimai:
REHEL arba Debian Webzy
Apratinės įrangos minmalūs reikalvimai:
Procesorius:
1,6 GHz
Dviejų branduolių
RAM:
4GB
DDR3
Laiva disko vieta:
10GB
Laisva "SWAP" vieta
30MB
ID: 61
MINIMALŪS REIKALAVIMAI KLEIANTAMS
Prorainės įrangos reikalavimai:
Operacinės:
Winows XP ir aukščiau
Ubuntu 12.04 (Kitos grafinės UNIX distribucijos Xubuntu, Lubuntu...)

#### 70: Bendradarbiaujančios sistemos
Sportinių rezultatų valdymo posistemė
Bilietų posistemė
Savanorių paskirstymo posistemė
Renginių transliavimo teisių valdymo posistemė
Sporto kompleksų užimtumo valdymo posistemė

#### 71: Komerciniai specializuoti programų paketai
Viešbučių garafiko paskirtymo paketas

#### 72: Numatoma darbo vietos aplinka
Numatoma įprastinė darbo vieta įmonėje

#### 73: Sistemos kūrimo terminai
Sistema turi būti parengta likus dviems mėniasiams iki Sočio Olimpinių žaidinių

#### 74: Sistemos kūrimo biudžetas
600 000Lt

### 75: Terminų žodynas
DB - duomenų bazė
IS - informacinė sistema
Intelekto kapitalas (Žmoginis kapitalas) – tai sukaupta investicijų į darbuotojų mokymus, kompetenciją.
Produktas - intelekto valdymo informacinė sistema
Veiklų biblioteka - veiklų ar įgūdžių, sudarančių darbus, sąrašas.
Darbų biblioteka - darbų, kurie susideda iš kelių veiklų, sąrašas.

### 77: Prielaidos
Prielaidos realizuojamos funkciniuose ir nefunkciniuose reikalavimuose

## 78: Funkciniai reikalavimai

### 79: Veiklos sfera

#### 80: Veiklos kontekstas
Apgyvendinimo sistema būtina norint tinkamai sukontroliuoti olimpinių žaidinių gyventojų, trenerių, aptarnaujančio personalo srautus. Jei sportininkams, treneriams tektų gyventi per toli sporto arenų reiktų rūpintis trasnportavimu kas sukeltų papildomų problemų.

#### 81: Veiklos padalinimas
Veikla skirstoma pagal vartotojus.
Apgyvandnimo darbuotojai naudoja veikloms susijusioms su apgyvendinimo funkciojomis įtakojančiomis visus vartotojus
Apgyvendinimo sistemos vartotojai naudojasi funkcijomis skirtomis savo asminės ar komandos rezervacijos valdymui

### 82: Produkto veiklos sfera

#### 83: Sistemos ribos
Sistema apribojama apgyvendinimo valdymu
Apribojama laike kuriuo jis bus naudojama (2mėn. prieš, per 1mėn. po Sočio olimpinių žaidynių)
Skirta tik įrenginiams turintiems priėjimą prie internto ar teisiogiai prie serverio
Gali būti atvaizduota tik per įrenginius palaikančius inteneto naršykles nesnesnes nei 4 metaI
Sistema priima tik diskrečius duomenis
Asmens duomenys yra tikrinami pasikliaujant išorine Olimpijados dalyvių duombaze

#### 84: Panaudojimo atvejų sąrašas

### 85: Funkciniai reikalavimai ir reikalavimai duomenims

#### 87: Funkciniai reikalavimai
Papildant asmens/rezervacijos duomenis jie turi būti pakeičiami tik pakitusiuose vietose
Darbuotojai privalo keisti savo darbinius slaptažodzius kas dvi savaitės
Duomazė turi laikyti visas pinignes sumas 64 bitų dydžio kitamuosiuose

#### 88: Reikalavimai duomenims
Duomenys turi būti dikretūs
Duomenų atnaujinimas darbuotojams turi būti priskirtas automatinis
Duomenys turi būti išsaugomi duombazėje

## 89: Nefunkciniai reikalavimai

### 90: Reikalavimai sistemos išvaizdai
Vienas iš pagrindinių reikalavimų yra reikalavimas, kad sistemos funkcijos būtų prieinamos per interneto naršyklę
Naudotojo sąsajos valdymo elementai turi būti standartiniai naršyklės palaikomi valdymo elementai.
Grafinė naudotojo sąsaja turi nevarginti vartotojų ryškiais elementais.
Sistemos naudotojo dinaminė rolė priklauso nuo projekto būsenos.

### 91: Reikalavimai panaudojamumui
Reikalavimų panaudojamumui sąrašas:
Sistema turi būti paprasta naudotis.
Sistemoje turi būti galimybė taisyti padarytas klaidas.
Sistemos naudotojo sąsaja turi būti angliška.
Turi būti galimybė pasižiūrėti raktinės informacijos paaiškinimus (pvz. vertinant gyventojų tipus, kokie padaliniai jiems tinkamesni)
Kur įmanoma, naudoti iškrentančius sąrašus

### 92: Reikalavimai vykdymo charakteristikoms
Suderinamas su Internet Explorer 7 ar vėlesne versija
Vienu metu su sistema turi būti įmanoma dirbti 100 žmonių

### 93: Reikalavimai veikimo sąlygoms
Sistema veiks bet kuriame kompiuteryje, turinčiame ryšį su IS serveriu.

### 94: Reikalavimai sistemos priežiūrai
Sistemos priežiūrai keliami reikalavimai:
Sistema turi būti realizuota taip, kad jos veikimui užtikrinti nereikėtų nuolatinio programuotojo įsikišimo (keičiantis organizacijos veiklos taisyklėms šis reikalavimas netaikomas).
Keičiantis organizacijos veiklos taisyklėms turi būti įmanoma adaptuoti sistemą prie naujų poreikių

### 95: Reikalavimai saugumui
Sistemos saugumui keliami reikalavimai:
Veiksmus su sistemoje kaupiamais duomenimis gali atlikti tik registruoti naudotojai;
Registruoti sistemos naudotojai gali atlikti veiksmus tik su tais duomenim, kuriais jie gali operuoti nekompiuterizuotoje formoje;

## 96: Projekto išeiga

### 98: Egzistuojantys sprendimai
Egzistuoja daug viešbučių rezervavimo sprendimų tarp jų eTuras. Deja siūlomas funkcionalumas netenkina sistemos reikalavimų, kadangi dalykinė sritis specifinė. Reikalinga klientus skirstyti į skirtingus tipus - sportininkai, treneriai, aptarnaujantis persionalas. Toks funkcionalumas neaptiktas egzistuojančiuose sprendimuose.

#### 100: Pagaminti komponentai, kurie gali būti naudoti
Pagamintų komponentų tinkančių pritaikyti sistemai.

#### 101: Galimas pakartotinis panaudojimas
Kai kurie sistemos komponentai, kaip registracija, autentifikavimas, autorizacija bus panaudoti pakartotinai iš ankstesnių kurtų sistemų.

### 102: Naujos problemos
Sistemos funkcijos bus prieinamos per interneto naršyklę. Kliento pusėje pagrindinė problema – būtinybė užtikrinti, kad naudojama naršyklė Internet Explorer 7 ar vėlesnė.
Pati sistema bus suinstaliuota centriniame serveryje vieną kartą, tad išpildžius techninei įrangai keliamus reikalavimus kitų problemų neturėtų būti.

#### 103: Problemos diegimo aplinkai
Padidės serverio apkrautumas. Problema galės būti išspręsta pagerinus centrinio serverio techninius duomenis.

### 106: Uždaviniai

#### 107: Sistemos pateikimo žingsniai
Visi sistemos pateikimo žingsniai išsamiai pateikiami detaliame projekto plane.

#### 108: Vystymo etapai
Pagrindiniai sistemos vystymo etapai:
- Paraiška – projekto tikslų bei reikalavimų suderinimas tarp jo užsakovo, vadovo ir vykdytojų;
- Darbų planas – projekto realizavimo darbų eigos, jų atlikimo terminų nustatymas;
- Projekto informacijos puslapis – sukurtas projekto informacijos puslapis, kuriame talpinama visa projekto vykdymo medžiaga.
- Reikalavimų specifikacija – projekto pagrindinių apribojimų nustatymas, funkcinių ir nefunkcinių reikalavimų sudarymas, išeigos apskaičiavimas;
- Architektūros specifikacija – projekto architektūros sudarymas panaudojimo atvejų, procesų ir realizacijos aspektais per UML diagramas;
- Detalios architektūros specifikacija – projekto detalios architektūros projektavimas;
- Testavimo planas – projekto testavimo darbų eigos sudarymas, testavimo metodų ir kriterijų parinkimas;
- Sistemos prototipas – realizuojamos sistemos supaprastinto varianto paruošimas;
- Naudotojo dokumentacija – išsamus naudojimosi sistema aprašymas;
- Programinės įrangos realizacija – sistemos programavimas bei pilnas ištestavimas;
- Sistemos įdiegimas – programinės įrangos instaliavimas ir sistemos parengimas naudojimui.

### 112: Rizikos

#### 114: Galimos sistemos kūrimo rizikos
Rizikos faktorius Tikimyb
s įvertinima
* Reikalavimų specifikacijos pasikeitimai realizavimo
je 10 Besivystantys naudotojo
lavimai 9 Pasikeitimai projekto plane – sutrumpinti darbų atlikimo terminai 8
mo terminai 8 Projekto vadovo ar vykdytojų pasikeitimas 8
jų pasikeitimas 8 Architektūros klaidų apti
realizavimo fazėje 8 * – įvertinimo skalė: 10 – rizika tikrai sukels problemas, 1 – rizika nesukels problemų.
izika nesukels problemų.

#### 116: Atsitiktinumų (rizikų planas)
Rizikos faktorius Problemos sprend
s Reikalavimų specifikacijos pasikeitimai realizavimo fazėje Sistema kuriama pagal užsakovo ir vykdytojo pasirašytą specifikaciją, kurios keitimas iki sistemos galutinio pridavimo įmanomas tik sutarus abiem pusėm. Nesant šiam sutarimui, pakeitimai atliekami sistemos vyst
tape. Besivystantys naudotojo reikalavimai Bus pateikiamas siste
rototipas

### 117: Kaina

### 118: Naudotojo dokumentacija ir apmokymas
Sistemos naudotojai bus informacinių sistemų kūrėjai profesionalai. Todėl pagrindinis akcentas ruošiant naudotojo vadovą bus sistemos funkcionalumas. Tuo tarpu aprašymų kaip naudotis sistema kiekis bus minimalus, kad neerzintų sistemos naudotojo dideliu kiekiu jam žinomos informacijos pateikimu.

### 119: Perspektyviniai reikalavimai
Apgyvendinimo sistemą bus galima panaudoti ir kitų, ateinančių metų olimpinių žaidinių apgyvendinimo IS kūrimui. Nors keičiasi ir vieta, ir pastatai, ir sezonas visus pakeitimus bus galima pritaikyti prie kuriamos IS.
