# IBM Rational DOORS, 21 May 2014

# Specification: Apgyvendinimo posistemė
- ReqIF.Name: Apgyvendinimo posistemė

## 48: Įvadas
Darbo tikslas sukurti sistemą galinčią kontroliuoti olimpinių žaidinių gyventojų srautus. Parinkti tinkamas apgyvendinimo vietas, nustatyti vizito trukmes, surinkti informaciją apie gyventoją.

### 49: Sistemos paskirtis

#### 50: Projekto kūrimos pagrindas
Sukurti sistemą galinčia aptarnauji olimpinių žaidinių gyventojų srautus ir juos nukreipti į tinkamos infrastruktūros pastatus.

#### 51: Sistemos tikslai
Sukurti išansktinės rezervacijos glaimybę.
Realizuoti rezervacijos valdymą.
Realizuoti lankytojų duomenų valdymą.
Turėti galimybę lankytojams pasiūlyti skirtingas infrastruktūras palei jų tipą.

### 53: Sistemos dalyviai

#### 55

#### 54: Užsakovai, pirkėjai ir kiti sistema suinteresuoti asmenys
Olimpinių žaidynių komitetas.

#### 56: Naudotojai
Olimpinių žaidinių administracija atsakinga už apgyvendinimą.
Registratūros darbuotojai.

## 113: Įvadas
ID: 48
- Section: 1

### 114: Sistemos paskirtis
ID: 49
- Section: 1.1

#### 115: Projekto kūrimos pagrindas
ID: 50
- Section: 1.1.1

#### 116: Sistemos tikslai
ID: 51
- Section: 1.1.2

### 117: Sistemos dalyviai
ID: 53
- Section: 1.2

#### 118: Užsakovai, pirkėjai ir kiti sistema suinteresuoti asmenys
ID: 54
- Section: 1.2.1

#### 119: Naudotojai
ID: 56
- Section: 1.2.2

## 120: Projekto apribojimai
Skirstomi į techninius ir netechninius reikalvaimus ID: 58
- Section: 2

### 121: Įpareigojantys apribojimai
Reikalavimai, kurių neįgyvedinus sistemos funkcinai ir nefunkciniai reikalavimai bus nepilnai ar visai neįgyvendinti ID: 59
- Section: 2.1

#### 122: Apribojimai sprendimui
Sprendimas ribojamas savo funkciniais ir nefunkciniais reikalaviamis Sprendimo funkcionalumas neturi persidengti su palaikančių ar sus sitema bendraujančių sistemų funkcionalumu ID: 60
- Section: 2.1.1

#### 123: Diegimo aplinka
MINIMALŪS REIKALVIMAI SERVERIAMS Nemažiau kaip trys paskirstyti serveriai Serveriai: Programinės įrangos reikalavimai: REHEL arba Debian Webzy Apratinės įrangos minmalūs reikalvimai: Procesorius: 1,6 GHz Dviejų branduolių RAM: 4GB DDR3 Laiva disko vieta: 10GB Laisva "SWAP" vieta 30MB ID: 61 MINIMALŪS REIKALAVIMAI KLEIANTAMS Prorainės įrangos reikalavimai: Operacinės: Winows XP ir aukščiau Ubuntu 12.04 (Kitos grafinės UNIX distribucijos Xubuntu, Lubuntu...) 2.1.3 Bendradarbiaujančios sistemos Sportinių rezultatų valdymo posistemė Bilietų posistemė Savanorių paskirstymo posistemė Renginių transliavimo teisių valdymo posistemė Sporto kompleksų užimtumo valdymo posistemė ID: 62
- Section: 2.1.2

#### 124: Komerciniai specializuoti programų paketai
Viešbučių garafiko paskirtymo paketas ID: 63
- Section: 2.1.4

#### 125: Numatoma darbo vietos aplinka
Numatoma įprastinė darbo vieta įmonėje ID: 64
- Section: 2.1.5

#### 126: Sistemos kūrimo terminai
Sitema turi būti parengta likus dviems mėniasiams iki Sočio Olimpinių žaidinių ID: 65
- Section: 2.1.6

#### 127: Sistemos kūrimo biudžetas
600 000Lt ID: 66
- Section: 2.1.7

### 128: Terminų žodynas
ID: 67
- Section: 2.2

### 129: Prielaidos
Prielaidos realizuojamos funkciniuose ir nefunkciniuose reikalavimuose ID: 69
- Section: 2.3

## 130: Funkciniai reikalavimai
ID: 70
- Section: 3

### 131: Veiklos sfera
ID: 71
- Section: 3.1

#### 132: Veiklos kontekstas
ID: 72
- Section: 3.1.1

#### 133: Veiklos padalinimas
ID: 73
- Section: 3.1.2

### 134: Produkto veiklos sfera
ID: 74
- Section: 3.2

#### 135: Sistemos ribos
ID: 75
- Section: 3.2.1

#### 136: Panaudojimo atvejų sąrašas
ID: 76
- Section: 3.2.2

### 137: Funkciniai reikalavimai ir reikalavimai duomenims
ID: 77
- Section: 3.3

#### 138: Funkciniai reikalavimai
ID: 78
- Section: 3.3.1

#### 139: Reikalavimai duomenims
ID: 80
- Section: 3.3.2

## 140: Nefunkciniai reikalavimai
ID: 81
- Section: 4

### 141: Reikalavimai sistemos išvaizdai
ID: 82
- Section: 4.1

### 142: Reikalavimai panaudojamumui
ID: 83
- Section: 4.2

### 143: Reikalavimai vykdymo charakteristikoms
ID: 84
- Section: 4.3

### 144: Reikalavimai veikimo sąlygoms
ID: 85
- Section: 4.4

### 145: Reikalavimai sistemos priežiūrai
ID: 86
- Section: 4.5

### 146: Reikalavimai saugumui
ID: 87
- Section: 4.6

## 147: Projekto išeiga
ID: 88
- Section: 5

### 148: Atviri klausimai
ID: 89
- Section: 5.1

### 149: Egzistuojantys sprendimai
ID: 90
- Section: 5.2

#### 150: Pagamintos sistemos, kurios gali būti nupirktos
ID: 92
- Section: 5.2.1

#### 151: Pagaminti komponentai, kurie gali būti naudoti
ID: 93
- Section: 5.2.2

#### 152: Galimas pakartotinis panaudojimas
ID: 94
- Section: 5.2.3

### 153: Naujos problemos
ID: 91
- Section: 5.3

#### 154: Problemos diegimo aplinkai
ID: 95
- Section: 5.3.1

#### 155: Kliudantys diegimo aplinkos apribojimai
ID: 96
- Section: 5.3.2

#### 156: Galimos naujos sistemos sukeltos problemos
ID: 97
- Section: 5.3.3

### 157: Uždaviniai
ID: 98
- Section: 5.4

#### 158: Sistemos pateikimo žingsniai
ID: 99
- Section: 5.4.1

#### 159: Vystymo etapai
ID: 100
- Section: 5.4.2

### 160: Pritaikymas
ID: 101
- Section: 5.5

#### 161: Reikalavimai esamų duomenų perkėlimui
ID: 102
- Section: 5.5.1

#### 162: Reikalingas duomenų transformavimas perkeliant į naują sistemą
ID: 103
- Section: 5.5.2

### 163: Rizikos
ID: 104
- Section: 5.6

#### 164: Galimos sistemos kūrimo rizikos
ID: 105
- Section: 5.6.1

#### 165: Atsitiktinumų (rizikų planas)
ID: 107
- Section: 5.6.2

### 166: Kaina
ID: 109
- Section: 5.7

### 167: Naudotojo dokumentacija ir apmokymas
ID: 110
- Section: 5.8

### 168: Perspektyviniai reikalavimai
ID: 111
- Section: 5.9

## 58: Projekto apribojimai
Skirstomi į techninius ir netechninius reikalvaimus.

### 59: Įpareigojantys apribojimai
Reikalavimai, kurių neįgyvedinus sistemos funkcinai ir nefunkciniai reikalavimai bus nepilnai ar visai neįgyvendinti.

#### 60: Apribojimai sprendimui
Sprendimas ribojamas savo funkciniais ir nefunkciniais reikalavimais.
Sprendimo funkcionalumas neturi persidengti su palaikančių ar sus sitema bendraujančių sistemų funkcionalumu.

#### 112

#### 61: Diegimo aplinka
MINIMALŪS REIKALAVIMAI KLEIANTAMS
Nemažiau kaip trys paskirstyti serveriai
Serveriai:
Programinės įrangos reikalavimai:
REHEL arba Debian Webzy
Apratinės įrangos minmalūs reikalvimai:
Procesorius:
1,6 GHz
Dviejų branduolių
RAM:
4GB
DDR3
Laiva disko vieta:
10GB
Laisva "SWAP" vieta
30MB
ID: 61
MINIMALŪS REIKALAVIMAI KLEIANTAMS
Prorainės įrangos reikalavimai:
Operacinės:
Winows XP ir aukščiau
Ubuntu 12.04 (Kitos grafinės UNIX distribucijos Xubuntu, Lubuntu...)

#### 62: Bendradarbiaujančios sistemos
Sportinių rezultatų valdymo posistemė
Bilietų posistemė
Savanorių paskirstymo posistemė
Renginių transliavimo teisių valdymo posistemė
Sporto kompleksų užimtumo valdymo posistemė

#### 63: Komerciniai specializuoti programų paketai
Viešbučių garafiko paskirtymo paketas

#### 64: Numatoma darbo vietos aplinka
Numatoma įprastinė darbo vieta įmonėje

#### 65: Sistemos kūrimo terminai
Sistema turi būti parengta likus dviems mėniasiams iki Sočio Olimpinių žaidinių

#### 66: Sistemos kūrimo biudžetas
600 000Lt

### 67: Terminų žodynas
DB - duomenų bazė
IS - informacinė sistema
Intelekto kapitalas (Žmoginis kapitalas) – tai sukaupta investicijų į darbuotojų mokymus, kompetenciją.
Produktas - intelekto valdymo informacinė sistema
Veiklų biblioteka - veiklų ar įgūdžių, sudarančių darbus, sąrašas.
Darbų biblioteka - darbų, kurie susideda iš kelių veiklų, sąrašas.

### 68: Svarbūs faktai

### 69: Prielaidos
Prielaidos realizuojamos funkciniuose ir nefunkciniuose reikalavimuose

## 70: Funkciniai reikalavimai

### 71: Veiklos sfera

#### 72: Veiklos kontekstas
Apgyvendinimo sistema būtina norint tinkamai sukontroliuoti olimpinių žaidinių gyventojų, trenerių, aptarnaujančio personalo srautus. Jei sportininkams, treneriams tektų gyventi per toli sporto arenų reiktų rūpintis trasnportavimu kas sukeltų papildomų problemų.

#### 73: Veiklos padalinimas

### 74: Produkto veiklos sfera

#### 75: Sistemos ribos

#### 76: Panaudojimo atvejų sąrašas

### 77: Funkciniai reikalavimai ir reikalavimai duomenims

#### 79

#### 78: Funkciniai reikalavimai

#### 80: Reikalavimai duomenims

## 81: Nefunkciniai reikalavimai

### 82: Reikalavimai sistemos išvaizdai
Vienas iš pagrindinių reikalavimų yra reikalavimas, kad sistemos funkcijos būtų prieinamos per interneto naršyklę
Naudotojo sąsajos valdymo elementai turi būti standartiniai naršyklės palaikomi valdymo elementai.
Grafinė naudotojo sąsaja turi nevarginti vartotojų ryškiais elementais.
Sistemos naudotojo dinaminė rolė priklauso nuo projekto būsenos.

### 83: Reikalavimai panaudojamumui
Reikalavimų panaudojamumui sąrašas:
Sistema turi būti paprasta naudotis.
Sistemoje turi būti galimybė taisyti padarytas klaidas.
Sistemos naudotojo sąsaja turi būti angliška.
Turi būti galimybė pasižiūrėti raktinės informacijos paaiškinimus (pvz. vertinant gyventojų tipus, kokie padaliniai jiems tinkamesni)
Kur įmanoma, naudoti iškrentančius sąrašus

### 84: Reikalavimai vykdymo charakteristikoms
Suderinamas su Internet Explorer 7 ar vėlesne versija
Vienu metu su sistema turi būti įmanoma dirbti 100 žmonių

### 85: Reikalavimai veikimo sąlygoms
Sistema veiks bet kuriame kompiuteryje, turinčiame ryšį su IS serveriu.

### 86: Reikalavimai sistemos priežiūrai
Sistemos priežiūrai keliami reikalavimai:
Sistema turi būti realizuota taip, kad jos veikimui užtikrinti nereikėtų nuolatinio programuotojo įsikišimo (keičiantis organizacijos veiklos taisyklėms šis reikalavimas netaikomas).
Keičiantis organizacijos veiklos taisyklėms turi būti įmanoma adaptuoti sistemą prie naujų poreikių

### 87: Reikalavimai saugumui
Sistemos saugumui keliami reikalavimai:
Veiksmus su sistemoje kaupiamais duomenimis gali atlikti tik registruoti naudotojai;
Registruoti sistemos naudotojai gali atlikti veiksmus tik su tais duomenim, kuriais jie gali operuoti nekompiuterizuotoje formoje;

## 88: Projekto išeiga

### 89: Atviri klausimai

### 90: Egzistuojantys sprendimai
Egzistuoja daug viešbučių rezervavimo sprendimų tarp jų eTuras. Deja siūlomas funkcionalumas netenkina sistemos reikalavimų, kadangi dalykinė sritis specifinė. Reikalinga klientus skirstyti į skirtingus tipus - sportininkai, treneriai, aptarnaujantis persionalas. Toks funkcionalumas neaptiktas egzistuojančiuose sprendimuose.

#### 92: Pagamintos sistemos, kurios gali būti nupirktos

#### 93: Pagaminti komponentai, kurie gali būti naudoti
Pagamintų komponentų tinkančių pritaikyti sistemai.

#### 94: Galimas pakartotinis panaudojimas
Kai kurie sistemos komponentai, kaip registracija, autentifikavimas, autorizacija bus panaudoti pakartotinai iš ankstesnių kurtų sistemų.

### 91: Naujos problemos
Sistemos funkcijos bus prieinamos per interneto naršyklę. Kliento pusėje pagrindinė problema – būtinybė užtikrinti, kad naudojama naršyklė Internet Explorer 7 ar vėlesnė.
Pati sistema bus suinstaliuota centriniame serveryje vieną kartą, tad išpildžius techninei įrangai keliamus reikalavimus kitų problemų neturėtų būti.

#### 95: Problemos diegimo aplinkai
Padidės serverio apkrautumas. Problema galės būti išspręsta pagerinus centrinio serverio techninius duomenis.

#### 96: Kliudantys diegimo aplinkos apribojimai
Nėra.

#### 97: Galimos naujos sistemos sukeltos problemos
Nėra.

### 98: Uždaviniai

#### 99: Sistemos pateikimo žingsniai
Visi sistemos pateikimo žingsniai išsamiai pateikiami detaliame projekto plane.

#### 100: Vystymo etapai
Pagrindiniai sistemos vystymo etapai:
- Paraiška – projekto tikslų bei reikalavimų suderinimas tarp jo užsakovo, vadovo ir vykdytojų;
- Darbų planas – projekto realizavimo darbų eigos, jų atlikimo terminų nustatymas;
- Projekto informacijos puslapis – sukurtas projekto informacijos puslapis, kuriame talpinama visa projekto vykdymo medžiaga.
- Reikalavimų specifikacija – projekto pagrindinių apribojimų nustatymas, funkcinių ir nefunkcinių reikalavimų sudarymas, išeigos apskaičiavimas;
- Architektūros specifikacija – projekto architektūros sudarymas panaudojimo atvejų, procesų ir realizacijos aspektais per UML diagramas;
- Detalios architektūros specifikacija – projekto detalios architektūros projektavimas;
- Testavimo planas – projekto testavimo darbų eigos sudarymas, testavimo metodų ir kriterijų parinkimas;
- Sistemos prototipas – realizuojamos sistemos supaprastinto varianto paruošimas;
- Naudotojo dokumentacija – išsamus naudojimosi sistema aprašymas;
- Programinės įrangos realizacija – sistemos programavimas bei pilnas ištestavimas;
- Sistemos įdiegimas – programinės įrangos instaliavimas ir sistemos parengimas naudojimui.

### 101: Pritaikymas

#### 102: Reikalavimai esamų duomenų perkėlimui

#### 103: Reikalingas duomenų transformavimas perkeliant į naują sistemą

### 104: Rizikos

#### 108

#### 105: Galimos sistemos kūrimo rizikos
Rizikos faktorius Tikimyb
s įvertinima
* Reikalavimų specifikacijos pasikeitimai realizavimo
je 10 Besivystantys naudotojo
lavimai 9 Pasikeitimai projekto plane – sutrumpinti darbų atlikimo terminai 8
mo terminai 8 Projekto vadovo ar vykdytojų pasikeitimas 8
jų pasikeitimas 8 Architektūros klaidų apti
realizavimo fazėje 8 * – įvertinimo skalė: 10 – rizika tikrai sukels problemas, 1 – rizika nesukels problemų.
izika nesukels problemų.

##### 106

#### 107: Atsitiktinumų (rizikų planas)
Rizikos faktorius Problemos sprend
s Reikalavimų specifikacijos pasikeitimai realizavimo fazėje Sistema kuriama pagal užsakovo ir vykdytojo pasirašytą specifikaciją, kurios keitimas iki sistemos galutinio pridavimo įmanomas tik sutarus abiem pusėm. Nesant šiam sutarimui, pakeitimai atliekami sistemos vyst
tape. Besivystantys naudotojo reikalavimai Bus pateikiamas siste
rototipas

### 109: Kaina

### 110: Naudotojo dokumentacija ir apmokymas
Sistemos naudotojai bus informacinių sistemų kūrėjai profesionalai. Todėl pagrindinis akcentas ruošiant naudotojo vadovą bus sistemos funkcionalumas. Tuo tarpu aprašymų kaip naudotis sistema kiekis bus minimalus, kad neerzintų sistemos naudotojo dideliu kiekiu jam žinomos informacijos pateikimu.

### 111: Perspektyviniai reikalavimai
Apgyvendinimo sistemą bus galima panaudoti ir kitų, ateinančių metų olimpinių žaidinių apgyvendinimo IS kūrimui. Nors keičiasi ir vieta, ir pastatai, ir sezonas visus pakeitimus bus galima pritaikyti prie kuriamos IS.

## 57

## 52
